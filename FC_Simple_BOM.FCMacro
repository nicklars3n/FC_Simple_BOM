import FreeCAD as App
import PySide2
import os
import json
import csv
from FastenerBase import FSBaseObject

def traverse_object(object, link_label="", link_descr=""):
    label = object.Label
    description = object.Label2

    # apply link label (App::Link)
    if link_label != "":
        label = link_label
    
    # apply link description (App::Link)
    if link_descr != "": # override description if provided
        description = link_descr

    # Classify object
    if object.TypeId == "App::Part":

        children = [object.getSubObject(name, retType=1) for name in object.getSubObjects()]

        return {
            "label": label,
            "description": description,
            "children": [
                y for child in children if (y := traverse_object(child)) is not None
            ]
        }
    
    elif object.TypeId == "App::DocumentObjectGroup":
        children = [object.getSubObject(name, retType=1) for name in object.getSubObjects()]
        
        return [
                y for child in children if (y := traverse_object(child)) is not None
            ]

    elif object.TypeId == "App::Link":
        return traverse_object(object.LinkedObject, link_label=label, link_descr=description)

    elif object.TypeId == "Part::FeaturePython":
        # Arrays
        if hasattr(object, 'ArrayType'):
            if object.ArrayType == "Circular Array":

                obj = traverse_object(object.SourceObject)
                return [obj] * object.Count
        
        # Fasteners
        if hasattr(object, 'Proxy'):
            if isinstance(object.Proxy, FSBaseObject):

                return {
                    "label": label,
                    "description": description,
                    "children": [],
                }

def dissolve_lists(object):
    # take lists in child and break down

    newchildren = []
    # break objects out of lists
    for child in object["children"]:
        if isinstance(child, list):
            for subchild in child:
                newchildren.append(subchild)
        else:
            newchildren.append(child)
        
    object["children"] = newchildren

    # next level
    for child in object["children"]:
        dissolve_lists(child)

def flatten(object, consolidated={}, label_prefix=""):
    # flatten the tree, removing assemblies, consolidating parts by description
    # labels are represented hierachically using dot separator

    label = object["label"]

    # apply label_prefix
    if label_prefix != "":
        label = label_prefix + "." + label

    if len(object["children"]) > 0:
        for child in object["children"]:
            flatten(child, consolidated, label)
    else:
        key = object["description"]
        if key == "":
            key = object["label"] # revert to label in absense of description

        if key in consolidated:
            consolidated[key]["instances"] += 1
            if label not in consolidated[key]["label"]: # only put unique labels
                consolidated[key]["label"].append(label)
        else:
            consolidated[key] = {
                "label": [label],
                "description": object["description"],
                "instances": 1,
            }

    return consolidated

def listify(object):
    lst = []
    for key in object:
        # object[key]["description"] = key
        
        lst.append({
            "label": ", ".join(object[key]["label"]),
            "description": object[key]["description"],
            "instances": object[key]["instances"],
        })

    return lst

def save(root_assem):
    direct = os.path.dirname(App.ActiveDocument.FileName)
    SaveName, Filter = PySide2.QtWidgets.QFileDialog.getSaveFileName(None, "Export BOM", direct, "Javascript Object Notation (*.json);;Comma Delimited (*.csv)")
    
    #testing
    # SaveName, Filter = ("C:/Users/nickl/repos/postie_bike/test.csv", "*.csv")
    # SaveName, Filter = ("C:/Users/nickl/repos/postie_bike/test.json", "*.json")

    print(f"Saving to: {SaveName} with filter {Filter}")

    if "*.json" in Filter:
        with open(SaveName, "w", encoding="utf-8") as file:
            json.dump(root_assem, file, indent=4)
    elif "*.csv" in Filter:
        with open(SaveName, "w", encoding="utf-8", newline="") as file:
            fieldnames = ["label", "description", "instances"]
            writer = csv.DictWriter(file, fieldnames=fieldnames)

            writer.writeheader()
            writer.writerows(root_assem)
            

if __name__=="__main__":
    doc = App.ActiveDocument

    buffer = []

    for RootObject in doc.RootObjects:
        ## Find Root Assembly
        if RootObject.TypeId == "App::Part" and RootObject.Type == "Assembly":
            root_assem = traverse_object(RootObject)
            break

    
    dissolve_lists(root_assem)
    # save(root_assem)

    flat = flatten(root_assem)
    list = listify(flat)
    save(list)
